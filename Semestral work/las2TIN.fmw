FME workspace las2TIN.fmw

Parameters:
- SourceDataset_LAS = D:\FAV\PDB\Semestral work\data\BENE03.laz   # Source ASPRS LAS File(s)
- DestDataset_COG = D:\FAV\PDB\Semestral work\data   # Destination GeoTIFF Folder
- DestDataset_SHAPEFILE_3 = D:\FAV\PDB\Semestral work\data   # Destination Esri Shapefile Folder
- DestDataset_SHAPEFILE = D:\FAV\PDB\Semestral work\data   # Destination Esri Shapefile Folder

Readers:
- LAS_1: LAS from $(SourceDataset_LAS)

Writers:
- COG_1: COG to $(DestDataset_COG)
- SHAPEFILE_1: SHAPEFILE to $(DestDataset_SHAPEFILE)
- SHAPEFILE_2: SHAPEFILE to $(DestDataset_SHAPEFILE_3)

LAS (reader LAS_1)
    -> TINGenerator [POINTS/LINES]
TINGenerator
    TOLERANCE = 100
    TRIANGLES -> benesov_exported (writer SHAPEFILE_1)
    TIN_SURFACE -> Scaler
Scaler
    RASTER_SCALING = Extents
    SCALE_ORIGIN = 0,0
    TEXT_LOC_ONLY = Location and Size
    XSCALE = 1
    YSCALE = 1
    ZSCALE = 0.1
    SCALED -> Inspector
    SCALED -> BENE (writer SHAPEFILE_2)
Inspector
BENE (writer SHAPEFILE_2)
    attributes: fme_basena varchar(50)
benesov_exported (writer SHAPEFILE_1)
    attributes: fme_basena varchar(50)
